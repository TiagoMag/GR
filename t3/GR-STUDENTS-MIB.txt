GR-STUDENTS-MIB DEFINITIONS ::= BEGIN

IMPORTS
	enterprises,
	MODULE-IDENTITY,
	OBJECT-TYPE,
	Counter32
		FROM SNMPv2-SMI
	OBJECT-GROUP
		FROM SNMPv2-CONF;

grMIB MODULE-IDENTITY
	LAST-UPDATED "202102161709Z"	-- Feb 16, 2021, 5:09:00 PM
	ORGANIZATION ""
	CONTACT-INFO
		""
	DESCRIPTION
		"MIB para eventos"
	REVISION "202102161709Z"	-- Feb 16, 2021, 5:09:00 PM
	DESCRIPTION
		"Initial version."
	-- 1.3.6.1.4.1.1
	::= { enterprises 1 }


-- Conformance
--

grMIBConf OBJECT IDENTIFIER 
	-- 1.3.6.1.4.1.1.3
	::= { grMIB 3 }

-- Groups
--

grMIBGroups OBJECT IDENTIFIER 
	-- 1.3.6.1.4.1.1.3.1
	::= { grMIBConf 1 }

-- Compliances
--

grMIBCompliances OBJECT IDENTIFIER 
	-- 1.3.6.1.4.1.1.3.2
	::= { grMIBConf 2 }

grMIBTable OBJECT-TYPE
	SYNTAX  SEQUENCE OF GrMIBEntry
	MAX-ACCESS not-accessible
	STATUS  current
	DESCRIPTION
		"Tabela de Eventos"
	-- 1.3.6.1.4.1.1.4
	::= { grMIB 4 }


grMIBEntry OBJECT-TYPE
	SYNTAX  GrMIBEntry
	MAX-ACCESS not-accessible
	STATUS  current
	DESCRIPTION
		"Entrada na tabela com informação do evento"
	INDEX {
		index }
	-- 1.3.6.1.4.1.1.4.1
	::= { grMIBTable 1 }


GrMIBEntry ::= SEQUENCE {

	index     Counter32,
	descricao OCTET STRING }


index OBJECT-TYPE
	SYNTAX  Counter32
	MAX-ACCESS read-only
	STATUS  current
	DESCRIPTION
		""
	-- 1.3.6.1.4.1.1.4.1.1
	::= { grMIBEntry 1 }


descricao OBJECT-TYPE
	SYNTAX  OCTET STRING
	MAX-ACCESS read-only
	STATUS  current
	DESCRIPTION
		"Descrição do evento"
	-- 1.3.6.1.4.1.1.4.1.2
	::= { grMIBEntry 2 }


tempoTable OBJECT-TYPE
	SYNTAX  SEQUENCE OF TempoTableEntry
	MAX-ACCESS not-accessible
	STATUS  current
	DESCRIPTION
		""
	-- 1.3.6.1.4.1.1.5
	::= { grMIB 5 }


tempoTableEntry OBJECT-TYPE
	SYNTAX  TempoTableEntry
	MAX-ACCESS not-accessible
	STATUS  current
	DESCRIPTION
		""
	INDEX {
		index }
	-- 1.3.6.1.4.1.1.5.1
	::= { tempoTable 1 }


TempoTableEntry ::= SEQUENCE {

	anos    INTEGER,
	meses   INTEGER,
	semanas INTEGER,
	dias    INTEGER,
	horas   INTEGER,
	minutos INTEGER }


anos OBJECT-TYPE
	SYNTAX  INTEGER
	MAX-ACCESS read-only
	STATUS  current
	DESCRIPTION
		"Anos"
	-- 1.3.6.1.4.1.1.5.1.1
	::= { tempoTableEntry 1 }


meses OBJECT-TYPE
	SYNTAX  INTEGER
	MAX-ACCESS read-only
	STATUS  current
	DESCRIPTION
		""
	-- 1.3.6.1.4.1.1.5.1.2
	::= { tempoTableEntry 2 }


semanas OBJECT-TYPE
	SYNTAX  INTEGER
	MAX-ACCESS read-only
	STATUS  current
	DESCRIPTION
		""
	-- 1.3.6.1.4.1.1.5.1.3
	::= { tempoTableEntry 3 }


dias OBJECT-TYPE
	SYNTAX  INTEGER
	MAX-ACCESS read-only
	STATUS  current
	DESCRIPTION
		""
	-- 1.3.6.1.4.1.1.5.1.4
	::= { tempoTableEntry 4 }


horas OBJECT-TYPE
	SYNTAX  INTEGER
	MAX-ACCESS read-only
	STATUS  current
	DESCRIPTION
		""
	-- 1.3.6.1.4.1.1.5.1.5
	::= { tempoTableEntry 5 }


minutos OBJECT-TYPE
	SYNTAX  INTEGER
	MAX-ACCESS read-only
	STATUS  current
	DESCRIPTION
		""
	-- 1.3.6.1.4.1.1.5.1.6
	::= { tempoTableEntry 6 }


mensagemTable OBJECT-TYPE
	SYNTAX  SEQUENCE OF MensagemEntry
	MAX-ACCESS not-accessible
	STATUS  current
	DESCRIPTION
		""
	-- 1.3.6.1.4.1.1.6
	::= { grMIB 6 }


mensagemEntry OBJECT-TYPE
	SYNTAX  MensagemEntry
	MAX-ACCESS not-accessible
	STATUS  current
	DESCRIPTION
		""
	INDEX {
		index }
	-- 1.3.6.1.4.1.1.6.1
	::= { mensagemTable 1 }


MensagemEntry ::= SEQUENCE {

	passado  OCTET STRING,
	presente OCTET STRING,
	futuro   OCTET STRING }


passado OBJECT-TYPE
	SYNTAX  OCTET STRING
	MAX-ACCESS read-only
	STATUS  current
	DESCRIPTION
		"Uma frase de alerta para quando o evento já aconteceu"
	-- 1.3.6.1.4.1.1.6.1.1
	::= { mensagemEntry 1 }


presente OBJECT-TYPE
	SYNTAX  OCTET STRING
	MAX-ACCESS read-only
	STATUS  current
	DESCRIPTION
		"Uma frase de alerta para quando o evento está a acontecer"
	-- 1.3.6.1.4.1.1.6.1.2
	::= { mensagemEntry 2 }


futuro OBJECT-TYPE
	SYNTAX  OCTET STRING
	MAX-ACCESS read-only
	STATUS  current
	DESCRIPTION
		"Uma frase de alerta para quando o evento é futuro"
	-- 1.3.6.1.4.1.1.6.1.3
	::= { mensagemEntry 3 }


grMIBBasicGroup OBJECT-GROUP
	OBJECTS {
		index,
		passado,
		presente,
		futuro }
	STATUS  current
	DESCRIPTION
		"Basic objects."
	-- 1.3.6.1.4.1.1.3.1.1
	::= { grMIBGroups 1 }

mibgrGroup OBJECT-GROUP
	OBJECTS {
		index,
		descricao,
		anos,
		meses,
		semanas,
		dias,
		horas,
		minutos,
		passado,
		presente,
		futuro }
	STATUS  current
	DESCRIPTION
		""
	-- 1.3.6.1.4.1.1.7
	::= { grMIB 7 }

END
